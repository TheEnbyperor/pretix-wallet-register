VAS-Data DEFINITIONS AUTOMATIC TAGS ::= BEGIN

	VASData ::= SEQUENCE {
		data SEQUENCE SIZE (0..16) OF DataType
	}

	DataType ::= SEQUENCE {
		dataFormat	IA5String (SIZE (0..4) ^ FROM ("A".."Z"|"0".."9")),
		data		OCTET STRING (SIZE (0..64))
	}

END
